#require 6.5100

// Revision history:
//
// 1.00
// - Initial release
//
// 1.01
// - Dialog mask for text or html output selection corrected
//
// 1.02
// - CSV export added after a suggestion of Christian Schlittler
// - File extension for text file output changed from .bom to .txt
//
// 1.03
// - Added missing description column in value mode.
//
// 1.04
// - List also Packages bei Value
//
// 1.05
// - 2012-03-01 change PartValue[], PartDevice[], PartPackage[], PartHeadline[], PartDescription[] to normal string. alf@cadsoft.de
//   numeric strings with only numericasl characters, sorts up to 8 characters!
//
// 1.06
// - 2012-05-25 support now populated variants
//              switch on/off attributes
//              is now the standard bom.ulp  alf@cadsoft.de
//
// 1.07
// - 2012-06-22 set correct variant
//
// 1.08
// - 2012-11-08 list different values of attributes
//
// 1.09
// - 2012-12-04 now can change the separator character for CSV files.
//              change the character in line Separator = ',';
//
// 1.10
// - 2014-08-07 extended to V7 hierarchical schematic
//
// 1.11
// - 2015-12-10 fixed handling descriptions containing TAB characters
//
// Revision: 1.11
//  - 2023-02-25 Changed the description

string Version = "1.12";

char   Separator = ';'; // 2012-12-04


#usage "en: <b>Export a Bill Of Material</b>\n"
           "<p>"
           "Generates a project's <i>Bill of Material</i> from the attributes assigned"
           "<p>"
           "<author>Author:<b> Cadsoft</b></author>"

// THIS PROGRAM IS PROVIDED AS IS AND WITHOUT WARRANTY OF ANY KIND, EXPRESSED OR IMPLIED

string HelpTextEN =
  "<b>How to generate the Bill Of Material</b>\n"
  "<p>\n"
  "<b>List type</b>\n"
  "<p>\n"
  "The <i>Bill Of Material</i> can be generated either as a list\n"
  "of parts (where every part is listed on a line of its own),\n"
  "or as a list of values, where all parts with the same value are grouped\n"
  "together in one line. Use the <b><u>P</u>arts</b> and <b><u>V</u>alues</b>\n"
  "radio buttons to select the list type.\n"
  "<p>\n"
  "<b>Output format</b>\n"
  "<p>\n"
  "Choose between pure ASCII <b><u>T</u>ext</b> format, <b><u>C</u>SV</b> or <b><u>H</u>TML</b>.\n"
  ;

string HelpTextDE =
  "<b>Erzeugen der Stückliste</b>\n"
  "<p>\n"
  "<b>Listen-Typ</b>\n"
  "<p>\n"
  "Die <i>Stückliste</i> kann entweder als Liste der Bauteile generiert werden\n"
  "(wobei jedes Bauteil in einer eigenen Zeile aufgeführt wird),\n"
  "oder als Liste der Werte, wobei alle Bauteile mit dem gleichen Wert in einer Zeile\n"
  "zusammengefasst werden. Mit den Radio-Buttons <b><u>B</u>auteile</b> und <b><u>W</u>erte</b>\n"
  "kann zwischen den beiden Listen-Typen gewählt werden.\n"
  "<p>\n"
  "<b>Ausgabeformat</b>\n"
  "<p>\n"
  "Wählen Sie zwischen reinem ASCII-<b><u>T</u>ext</b>, <b><u>C</u>SV</b> oder <b><u>H</u>TML</b>"
  "-Format.\n"
  ;

string I18N[] = {
  "en\v"
  "de\v"
  ,
  "<hr><b>ERROR: No schematic!</b><p>\nThis program can only work in the schematic editor.\v"
  "<hr><b>FEHLER: Kein Schaltplan!</b><p>\nDieses Programm kann nur in einem Schaltplan verwendet"
  " werden.\v"
  ,
  "Part\tValue\tDevice\tPackage\tDescription\v"
  "Bauteil\tWert\tDevice\tPackage\tDescription\v"
  ,
  "Qty\tValue\tDevice\tPackage\tParts\v"      // 2011-04-08
  "Menge\tWert\tDevice\tGehäuse\tBauteile\v"  // 2011-04-08
  ,
  "Partlist exported from %s at %s\v"
  "Stückliste exportiert aus %s am %s\v"
  ,
  "Bill Of Material - Preview\v"
  "Stückliste - Vorschau\v"
  ,
  "-Close\v"
  "-Schließen\v"
  ,
  "Save Bill Of Material\v"
  "Stückliste speichern\v"
  ,
  "File '\v"
  "Datei '\v"
  ,
  "' exists\n\nOverwrite?\v"
  "' existiert\n\nÜberschreiben?\v"
  ,
  "+&Yes\v"
  "+&Ja\v"
  ,
  "-&No\v"
  "-&Nein\v"
  ,
  "&No\v"
  "&Nein\v"
  ,
  "Name already defined!\v"
  "Name ist bereits definiert!\v"
  ,
  " Header\v"
  " Spaltenüberschrift\v"
  ,
  "&Name:\v"
  "&Name:\v"
  ,
  "+OK\v"
  "+OK\v"
  ,
  "Name can't be empty!\v"
  "Name kann nicht leer sein!\v"
  ,
  "-Cancel\v"
  "-Abbrechen\v"
  ,
  "&Headers\v"
  "&Spaltenüberschriften\v"
  ,
  "Bill Of Material - Help\v"
  "Stückliste - Hilfe\v"
  ,
  "Bill Of Material\v"
  "Stückliste\v"
  ,
  "List type\v"
  "Listen-Typ\v"
  ,
  "&Parts\v"
  "&Bauteile\v"
  ,
  "&Values\v"
  "&Werte\v"
  ,
  "Output format\v"
  "Ausgabeformat\v"
  ,
  "&Text\v"
  "&Text\v"
  ,
  "&CSV\v"
  "&CSV\v"
  ,
  "&HTML\v"
  "&HTML\v"
  ,
  "&Digikey\v"
  "&Digikey\v"
  ,
  "+Vie&w\v"
  "+&Vorschau\v"
  ,
  "&Save...\v"
  "&Speichern...\v"
  ,
  "H&elp\v"
  "H&ilfe\v"
  ,
  "Current &variant \v"
  "Aktuelle &Variante \v"
  ,
  "List &attributes\v"
  "&Attribute auflisten\v"
  };
int Language = strstr (I18N [0], language ()) / 3;


string tr (string s)
{
  string t = lookup (I18N, s, Language, '\v');
  return t ? t : s;
}


if (!schematic)
{
  dlgMessageBox (usage + tr ("<hr><b>ERROR: No schematic!</b><p>\nThis program can only work in"
                 " the schematic editor."));
  exit (1);
}

string SeparatorString;
int     NumParts;
numeric string Lines[];
numeric string PartName[];
string  PartValue[], PartDevice[], PartPackage[], PartHeadline[];
numeric string PartDescription [];
int     PartValueOn[];
int     Selected;

string CurrentVariant = "";
string Variants[] = { "" };  // 2012-04-16
int    cntVD = 0;
int    VDsel = 0;


// cwi: Added arrays for an arbitraty number of attributes.
int UseAttributes = 1;
int FoundAttributes = 0;            // # of different attribute names found in schematic.
numeric string AttributesList[];    // Sorted list of all attributes found in the schematic.
numeric string PartAttributes[];    // Adjusted list of attributes per part.

enum { ltParts, ltValues };         // List Types
enum { ofText, ofCSV, ofHTML , ofDigikey};     // Output Formats
int ListType = 0;
int OutputFormat = 0;


string StripWhiteSpace (string s)
{
  while (s && isspace (s[0]))
    s = strsub (s, 1);
  while (s && isspace (s[strlen (s) - 1]))
    s = strsub (s, 0, strlen (s) - 1);
  return s;
}

string ReplaceTabs(string s)
{
  int i;
  while ((i = strchr(s, '\t')) >= 0)
        s = strsub(s, 0, i) + "\\t" + strsub(s, i + 1);
  return s;
}

// Collect part data from the schematic.
//
// Arguments: -
//
// Returns:   NumParts            - # of found parts
//            ParteName[]
//            PartValue[]
//            PartDevice[]
//            PartPackage[]
//            PartHeadline[]
//            PartDescription []
//            PartValueOn[]      - 0=part value off, 1= part value on, 2=override with attr. VAL
//            FoundAttributes     - # of different attribute names found in schematic.
//            AttributesList[]   - Sorted list of all attributes found in the schematic.
//            PartAttributes[]   - Adjusted list of attributes per part.

void CollectPartData (string var)
{
  int Found = 0;
  int i;
  string attr[];

  NumParts = 0;

  // First, collect the names of all available attributes.
  FoundAttributes = 0;
  if (UseAttributes) {
    schematic (SCH)
    {
      SCH.allparts (P) // 2014-08-07
      {
        if (P.device.package)
        {
          if (P.populate)
          {
            P.attributes (A)
            {
              if (0 == FoundAttributes)
              {
                // First one
                AttributesList[0] = A.name;
                FoundAttributes = 1;
              }
              else
              {
                Found = 0;
                for (i = 0; i < FoundAttributes; i ++)
                {
                  if (A.name == AttributesList[i])
                  {
                    // Found an already listed atrribute
                    Found = 1;
                    break;
                  }
                }
                if (0 == Found)
                {
                  // Attribute not listed, add at the end.
                  AttributesList[FoundAttributes] = A.name;
                  FoundAttributes ++;
                }
              }
            }
          }
        }
      }
    }
    sort (FoundAttributes, AttributesList);
  }
  // Second, collect all data
  schematic (SCH)
  {
    SCH.allparts (P)
    {
      if (P.device.package)
      {
        if (P.populate)
        {
          PartName[NumParts] = P.name;
          PartValue[NumParts] = P.value;
          PartDevice[NumParts] = P.device.name;
          PartPackage[NumParts] = P.device.package.name;
          PartHeadline[NumParts] = ReplaceTabs(P.device.headline);
          // currently not used:
          // PartDescription[NumParts] = ReplaceTabs(P.device.description);
          PartValueOn[NumParts] = P.device.value == "On";
          // Zero all strings
          for (i = 0; i < FoundAttributes; i ++)
            attr[i] = "";
          P.attributes(A)
          {
            for (i = 0; i < FoundAttributes; i ++)
              if (A.name == AttributesList[i])
              {
                attr[i] = A.value;
                break;
              }
            if ("VALUE" == A.name && 0 < strlen (A.value))
             // Override old fashioned value information!
            PartValueOn[NumParts] = 2;
          }
          PartAttributes[NumParts] = strjoin(attr, Separator);
          NumParts ++;
        }
      }
    }
  }
}


void GeneratePartList(void)
{
  int NumLines = 0;
  string attr[], s;

  if (UseAttributes) s = strjoin(AttributesList, '\t');
  Lines[NumLines ++] = tr ("Part\tValue\tDevice\tPackage\tDescription\t") + s;
  for (int i = 0; i < NumParts; i ++)
  {
    strsplit (attr, PartAttributes[i], Separator);
    if (UseAttributes) s = strjoin(attr, '\t');
    Lines[NumLines] = PartName[i] + "\t" + PartValue[i] + "\t" + PartDevice[i] + "\t" +
                       PartPackage[i] + "\t" + PartHeadline[i] + "\t" + s;
    NumLines ++;
  }
  Lines[NumLines] = "";
}


// Generate list with one entry per value.
// 'VALUE' is replaced by the value of attribute 'VAL', if existing.

void GenerateValueList (void)
{
  int NumLines = 0;
  int Index [];
  string attr[], s, s_val;

  if (UseAttributes) s = strjoin(AttributesList, '\t');

  // 2010-04-17 cwi: Included description.
  Lines[NumLines ++] = tr ("Qty\tValue\tDevice\tPackage\tParts\tDescription\t") + s;                 // 2011-04-08
  sort (NumParts, Index, PartValue, PartDevice, PartPackage, PartAttributes, PartName, PartHeadline); // 2011-11-08 Partattribute jetzt nach Package alf@cadsoft.de
  for (int n1 = 0, n2 = 0; ++ n2 <= NumParts; )
  {
    int i1 = Index [n1];
    strsplit (attr, PartAttributes[i1], Separator);
    if (UseAttributes) s = strjoin(attr, '\t');
    s_val = attr[i1];
    if (n2 < NumParts)
    {
      int i2 = Index [n2]; // 2012-11-08
      strsplit (attr, PartAttributes[i2], Separator);
      if (PartValue[i1] == PartValue[i2] && PartDevice[i1] == PartDevice[i2] && PartAttributes[i1] == PartAttributes[i2]) // 2012-11-08 check diffent values of attributes
        continue;
    }
    string Quantity;
    sprintf (Quantity, "%d", n2 - n1);
    Lines[NumLines] = Quantity + "\t" + PartValue[i1] + "\t" + PartDevice[i1] + "\t" + PartPackage[i1] + "\t";
    for (;;)
    {
      Lines[NumLines] += PartName[i1];
      if (++n1 < n2)
      {
        i1 = Index [n1];
        Lines[NumLines] += ", ";
      }
      else
        break;
    }
    // cwi: add extra information from attributes
    // 2010-04-17 cwi: Included description.
    Lines[NumLines] += "\t" + PartHeadline[i1] + "\t" + s;
    NumLines ++;
  }
  Lines[NumLines] = "";
}


void GenerateList (void)
{
  switch (ListType)
  {
    case ltParts:  GeneratePartList (); break;
    case ltValues: GenerateValueList (); break;
  }
}


string MakeListHeader (void)
{
  string s;
  schematic(SCH)
    sprintf (s, tr ("Partlist exported from %s at %s"), SCH.name, t2string (time ()));
  return s;
}

string StrReplace(string s, string src, string dst)
{
  int i;
  while ((i = strstr(s, src)) >= 0) {
        s = strsub(s, 0, i) + dst + strsub(s, i + strlen(src));
  }
  return s;
}

string PreprocessCSVLine(string s)
{
  // Preprocess a CSV string to replace all commas outside double quotes with line feeds
  // Also remove all quotes
  int insideQuotes = 0;
  string processed = "";
  for (int i = 0; i < strlen(s); i ++) {
    string substr = strsub(s, i, 1);
    if (substr == "\"") {
      insideQuotes = !insideQuotes;
    } else if (substr == "," && !insideQuotes) {
      processed += "\n";
      continue;
    } else {
      processed += substr;
    }
  }
  return processed;
}

int StrFindIndex(string s, string src, char sep)
{
  string a [];
  int n = strsplit(a, s, sep);
  for (int i = 0; i < n; i ++) {
    if (a[i] == src) {
      return i;
    }
  }
  return -1;
}

real ValFromString(string s, string unit)
{
  // Remove all spaces
  s = StrReplace(s, " ", "");
  // All possible units and their multipliers
  string scales [] =    { "p",   "P",   "n",  "N",  "u",  "U",  "µ",  "m",  "k", "K", "M" , ""  };
  real multipliers [] = { 1e-12, 1e-12, 1e-9, 1e-9, 1e-6, 1e-6, 1e-6, 1e-3, 1e3, 1e3, 1e6 , 1.0 };
  // Look for the right scale and extract the value
  string suffix = "";
  int n = 0;
  for (int j = 0; j < 2; j++) {
    if (j == 0) {
      // Try all the scales with the unit stuck behind
      suffix = unit;
      n = 12;
    } else {
      // Try all the scales on their own
      suffix = "";
      n = 11;
    }
    for (int i = 0; i < n; i ++) {
      string scale = scales[i] + suffix;
      if (strstr(s, scale) > 0) {
        if (strchr(s, '.') > 0) {
          // The value already contains a decimal point, no need to add another one
          s = StrReplace(s, scale, "");
        } else {
          // The value does not contain a decimal point, add one
          s = StrReplace(s, scale, ".");
        }
        return strtod(s) * multipliers[i];
      }
    }
  }

  return 0.0;
}

string MakeListText(void)
{
  int l, Width [];
  string List;
  int numHeaders;

  for (l = 0; Lines[l]; l ++)
  {
    string a [];
    for (int n = strsplit (a, Lines[l], '\t'); n --; )
      Width [n] = max (Width [n], strlen (a [n]));
  }

  List = MakeListHeader () + "\n\n";

  for (l = 0; Lines[l]; l ++)
  {
    string line, a [];

    int n = strsplit (a, Lines[l], '\t');
    if (l == 0)
      numHeaders = n;
    else
      n = numHeaders; // for the hidden key!
    for (int i = 0; i < n; i ++)
    {
      string s;

      sprintf (s, "%s%-*s", line ? " " : "", Width [i], a [i]);
      line += s;
    }
    List += line + "\n";
  }
  return List;
}


// 2008-11-24 Christian Schlittler:
// Make comma-serparated list, with all values double-quoted.

string MakeListCSV (void)
{
  string List;
  int numHeaders;

  for (int l = 0; Lines[l]; l ++)
  {
    string a [];
    int n = strsplit (a, Lines[l], '\t');
    if (l == 0)
      numHeaders = n;
    else
      n = numHeaders; // for the hidden key!
    for (int i = 0; i < n; i ++)
      List += "\"" + a[i] + "\"" + SeparatorString;
    List += "\n";
  }
  return List;
}

string MakeListDigikey (void)
{
  string comps_dk_pn [];
  string comps_mf_pn [];
  string comps_refdes [];
  int comps_qty [];
  int num_comps = 0;
  string list;
  int numHeaders;
  string a [];
  string dk_pns [];
  string mf_pns [];
  int dk_pn_index;
  int mf_pn_index;
  int parts_index;
  int qty_index;
  int device_index;
  int value_index;
  string bad_parts;

  // Find the path of the script
  string paths [];
  int n = strsplit (paths, argv[0], '/');
  string path = "";
  for (int i = 0; i < n - 1; i++) {
    path += paths[i] + '/';
  }

  // Load the resistor database
  string res_db [];
  int n_res = 0;
  n_res = fileread(res_db, path + "thick_film_resistors.csv");
  int res_value_index = StrFindIndex(PreprocessCSVLine(res_db[0]), "Resistance", '\n');
  int res_mf_pn_index = StrFindIndex(PreprocessCSVLine(res_db[0]), "Mfr Part #", '\n');
  int res_size_index = StrFindIndex(PreprocessCSVLine(res_db[0]), "Package / Case", '\n');
  int res_tol_index = StrFindIndex(PreprocessCSVLine(res_db[0]), "Tolerance", '\n');
  int res_stock_index = StrFindIndex(PreprocessCSVLine(res_db[0]), "Stock", '\n');

  // Load the capacitor database
  string cap_db [];
  int n_caps = 0;
  n_caps = fileread(cap_db, path + "ceramic_capacitors.csv");
  int cap_value_index = StrFindIndex(PreprocessCSVLine(cap_db[0]), "Capacitance", '\n');
  int cap_voltage_index = StrFindIndex(PreprocessCSVLine(cap_db[0]), "Voltage - Rated", '\n');
  int cap_mf_pn_index = StrFindIndex(PreprocessCSVLine(cap_db[0]), "Mfr Part #", '\n');
  int cap_size_index = StrFindIndex(PreprocessCSVLine(cap_db[0]), "Package / Case", '\n');
  int cap_tempco_index = StrFindIndex(PreprocessCSVLine(cap_db[0]), "Temperature Coefficient", '\n');
  int cap_stock_index = StrFindIndex(PreprocessCSVLine(cap_db[0]), "Stock", '\n');

  // Load the inductor database
  string ind_db [];
  int n_inds = 0;
  n_inds = fileread(ind_db, path + "fixed_inductors.csv");
  int ind_value_index = StrFindIndex(PreprocessCSVLine(ind_db[0]), "Inductance", '\n');
  int ind_current_index = StrFindIndex(PreprocessCSVLine(ind_db[0]), "Current Rating (Amps)", '\n');
  int ind_mf_pn_index = StrFindIndex(PreprocessCSVLine(ind_db[0]), "Mfr Part #", '\n');
  int ind_size_index = StrFindIndex(PreprocessCSVLine(ind_db[0]), "Package / Case", '\n');
  int ind_stock_index = StrFindIndex(PreprocessCSVLine(ind_db[0]), "Stock", '\n');


  // Figure out which columns we want to keep or reject, and translate
  // the header name to the name expected by Digikey.
  dk_pn_index = StrFindIndex(Lines[0], "DK_PN", '\t');
  mf_pn_index = StrFindIndex(Lines[0], "MF_PN", '\t');
  parts_index = StrFindIndex(Lines[0], "Parts", '\t');
  qty_index = StrFindIndex(Lines[0], "Qty", '\t');
  device_index = StrFindIndex(Lines[0], "Device", '\t');
  value_index = StrFindIndex(Lines[0], "Value", '\t');
  if (dk_pn_index == -1) {
    dlgMessageBox ("None of the parts has a Digikey part number. Please make sure at least one part has a DK_PN attribute.");
    return "";
  } 
  if (mf_pn_index == -1) {
    dlgMessageBox ("None of the parts has a manufacturer part number. Please make sure at least one part has a MF_PN attribute.");
    return "";
  }

  // Now we can output values for each part.
  for (int l = 1; Lines[l]; l ++)
  {
    int n = strsplit (a, Lines[l], '\t');
    string dk_pn = a[dk_pn_index];
    string mf_pn = a[mf_pn_index];
    string parts = a[parts_index];
    string device = a[device_index];
    int quantity = strtod(a[qty_index]);
    string value = a[value_index];
    string prefix = "";
    string type = "";

    // For resistors, inductors and capacitors, try to build a part number from the database
    if (strsub(device, 0, 9) == "R-US_CHIP") {
      prefix = "R-US_CHIP";
    }
    if (strsub(device, 0, 6) == "R_CHIP") {
      prefix = "R-CHIP";
    }
    if (strsub(device, 0, 6) == "L_CHIP") {
      prefix = "L_CHIP";
    }
    if (strsub(device, 0, 6) == "C_CHIP") {
      prefix = "C_CHIP";
    }
    if (prefix != "") {
      string size = strsub(device, strlen(prefix) + 1, 4);
      string type = strsub(device, 0, 1);

      /*
       * RESISTORS
       */

      if (type == "R") {
        real resistance = ValFromString(value, "R");
        // Look up the part in the database
        int best_is_1pct = 0;
        int best_stock = 0;
        for (int i = 1; i < n_res; i ++) {
          string r [];
          strsplit (r, PreprocessCSVLine(res_db[i]), '\n');
          real res_value = ValFromString(r[res_value_index], "Ohms");
          string res_size = strsub(r[res_size_index], 0, 4);
          string res_mf_pn = r[res_mf_pn_index];
          string dbg1;
          if (res_size == size && abs(res_value - resistance) < 1.0e-13) {
            int res_is_1pct = (r[res_tol_index] == "±1%");
            int res_stock = strtod(StrReplace(r[res_stock_index], ",", ""));
            // Prefer 1% over other types, and prefer parts with stock over parts without stock.
            if (res_is_1pct > best_is_1pct || (res_stock > best_stock)) {
              mf_pn = res_mf_pn;
              best_is_1pct = res_is_1pct;
              best_stock = res_stock;
            }
          }
        }
      }

      /*
       * CAPACITORS
       */
      if (type == "C") {
        // Separate value and voltage
        string b [];
        real voltage;
        real capacitance;
        n = strsplit (b, value, ' ');
        capacitance = ValFromString(b[0], "F");
        if (n == 2) {
          voltage = ValFromString(b[1], "V");
        } else {
          // Require at least 4V for ceramic capacitors
          voltage = 4.0;
        }
        // Now we can look up the part in the database
        int best_is_np0 = 0;
        int best_stock = 0;
        for (int i = 1; i < n_caps; i ++) {
          string c [];
          strsplit (c, PreprocessCSVLine(cap_db[i]), '\n');
          real cap_value = ValFromString(c[cap_value_index], "F");
          real cap_voltage = ValFromString(c[cap_voltage_index], "V");
          string cap_size = strsub(c[cap_size_index], 0, 4);
          string cap_mf_pn = c[cap_mf_pn_index];
          if (cap_size == size && cap_voltage >= voltage && abs(cap_value - capacitance) < 1.0e-13) {
            int cap_is_np0 = (c[cap_tempco_index] == "C0G, NP0");
            int cap_stock = strtod(StrReplace(c[cap_stock_index], ",", ""));
            // Prefer NP0 over other types, and prefer parts with stock over parts without stock.
            if (cap_is_np0 > best_is_np0 || (cap_stock > best_stock)) {
              mf_pn = cap_mf_pn;
              best_is_np0 = cap_is_np0;
              best_stock = cap_stock;
            }
          }
        }
      }

      /*
       * INDUCTORS
       */
      if (type == "L") {
        // Separate value and current
        string b [];
        real current;
        real inductance;
        n = strsplit (b, value, ' ');
        inductance = ValFromString(b[0], "H");
        if (n == 2) {
          current = ValFromString(b[1], "A");
        } else {
          // Any current is fine if not specicified
          current = 0.0;
        }
        // Now we can look up the part in the database
        int best_stock = 0;
        for (int i = 1; i < n_inds; i ++) {
          string l [];
          strsplit (l, PreprocessCSVLine(ind_db[i]), '\n');
          real ind_value = ValFromString(l[ind_value_index], "H");
          real ind_current = ValFromString(l[ind_current_index], "A");
          string ind_size = strsub(l[ind_size_index], 0, 4);
          string ind_mf_pn = l[ind_mf_pn_index];
          if (ind_size == size && ind_current >= current && abs(ind_value - inductance) < 1.0e-13) {
            int ind_stock = strtod(StrReplace(l[ind_stock_index], ",", ""));
            // Prefer parts with stock over parts without stock
            if (ind_stock > best_stock) {
              mf_pn = ind_mf_pn;
              best_stock = ind_stock;
            }
          }
        }
      }

    }

    if (dk_pn == "" && mf_pn == "") {
      bad_parts += ", " + a[parts_index];
    } else {
      // We may need to order multiple parts for a single part in the schematic. Do the split here
      int n_dk = strsplit (dk_pns, dk_pn, ',');
      int n_mf = strsplit (mf_pns, mf_pn, ',');
      if (n_dk != n_mf) {
        dlgMessageBox ("The number of Digikey part numbers and manufacturer part numbers do not match for part " + a[parts_index]);
      }
      for (int i = 0; i < n_dk; i++) {
        dk_pn = StrReplace(dk_pns[i], " ", "");;
        mf_pn = StrReplace(mf_pns[i], " ", "");;
        if (dk_pn != "N/A" && mf_pn != "N/A") {
          comps_dk_pn[num_comps] = dk_pn;
          comps_mf_pn[num_comps] = mf_pn;
          comps_refdes[num_comps] = parts;
          comps_qty[num_comps] = quantity;
          num_comps++;
        }
      }
    }
  }

  if (bad_parts != "") {
    dlgMessageBox (tr ("The following parts have no Digikey part number:\n\n") + strsub(bad_parts, 2));
  }

  // Combine the parts that have the same part number
  for (int c1 = 0; c1 < num_comps; c1++) {
    if (comps_qty[c1] == 0) {
      continue;
    }
    for (int c2 = c1 + 1; c2 < num_comps; c2++) {
      if (comps_qty[c2] == 0) {
        continue;
      }
      if (comps_dk_pn[c1] == comps_dk_pn[c2] &&
          comps_mf_pn[c1] == comps_mf_pn[c2]) {
        comps_refdes[c1] += ", " + comps_refdes[c2];
        comps_qty[c1] += comps_qty[c2];
        comps_qty[c2] = 0;
      }
    }
  }

  // Create the list string.
  list += "\"Digi-Key Part Number\", ";
  list += "\"Manufacturer Part Number\", ";
  list += "\"Reference Designator\", ";
  list += "\"Quantity1\", ";
  list += "\n";
  for (int m = 0; m < num_comps; m++) {
    if (comps_qty[m] == 0) {
      continue;
    }
    string line = "";
    sprintf(line, "\"%s\", \"%s\", \"%s\", \"%d\"", comps_dk_pn[m], comps_mf_pn[m], comps_refdes[m], comps_qty[m]);
    list += line + "\n";
  }

  return list;
}


string MakeListHTML (void)
{
  string List;
  int numHeaders;

  List = "<b>" + MakeListHeader() + "</b>\n<p>\n";
  List += "<table>\n";
  for (int l = 0; Lines[l]; l++)
  {
    List += "<tr>";
    string a [];
    int n = strsplit (a, Lines[l], '\t');
    if (l == 0)
      numHeaders = n;
    else
      n = numHeaders; // for the hidden key!
    for (int i = 0; i < n; i ++)
    {
      if (l == 0)
        a[i] = "<b>" + a[i] + "</b>";
      List += "<td>" + a[i] + "</td>";
    }
    List += "</tr>\n";
  }
  List += "</table>\n";
  return List;
}


string MakeList (void)
{
  switch (OutputFormat)
  {
    case ofText: return MakeListText(); break;
    case ofCSV:  return MakeListCSV(); break;
    case ofHTML: return MakeListHTML(); break;
    case ofDigikey:  return MakeListDigikey(); break;
  }
  return "";
}


void ViewList (void)
{
  dlgDialog (tr ("Bill Of Material - Preview"))
  {
    string s = MakeList ();
    if (OutputFormat == ofText || OutputFormat == ofCSV || OutputFormat == ofDigikey)
      s = "<pre>" + s + "</pre>";
    dlgHBoxLayout dlgSpacing (400);
    dlgHBoxLayout
    {
      dlgVBoxLayout dlgSpacing (300);
      dlgTextView (s);
    }
    dlgHBoxLayout
    {
      dlgStretch (1);
      dlgPushButton (tr ("-Close")) dlgReject ();
    }
  };
}


void SaveList (void)
{
  // 2008-11-24 cwi:
  // - Added new format extension .csv
  // - Changed from .bom to .txt for text format.
  string FileName;
  string FileExt;

  switch (OutputFormat)
  {
    case ofText: FileExt = ".txt"; break;
    case ofHTML: FileExt = ".html"; break;
    case ofCSV:  FileExt = ".csv"; break;
    case ofDigikey:  FileExt = ".csv"; break;
  }
  schematic(SCH) FileName = filesetext (SCH.name, FileExt);
  FileName = dlgFileSave (tr ("Save Bill Of Material"), FileName);
  if (FileName)
  {
    string a [];
    if (!fileglob (a, FileName) || dlgMessageBox (tr ("File '") + FileName +
        tr ("' exists\n\nOverwrite?"), tr("+&Yes"), tr("-&No")) == 0)
    {
      output (FileName, "wt")
      {
        printf ("%s", MakeList ()); // using "%s" to avoid problems if list contains any '%'
      }
    }
  }
}


void DisplayHelp (void)
{
  dlgDialog (tr ("Bill Of Material - Help"))
  {
    dlgHBoxLayout dlgSpacing (400);
    dlgHBoxLayout
    {
      dlgVBoxLayout dlgSpacing (300);
      dlgTextView (language () == "de" ? HelpTextDE : HelpTextEN);
    }
    dlgHBoxLayout
    {
      dlgStretch (1);
      dlgPushButton (tr ("-Close"))
      dlgReject ();
    }
  };
}


schematic(SCH) {
  sprintf(SeparatorString, "%c", Separator);
  CurrentVariant = variant();
  SCH.variantdefs(VD) {
    if (CurrentVariant == VD.name) VDsel = cntVD;
    sprintf(Variants[cntVD], "%s", VD.name);
    cntVD++;
  }
}

setvariant(CurrentVariant);
CollectPartData(CurrentVariant);
GenerateList();

dlgDialog (tr ("Bill Of Material"))
{
  dlgHBoxLayout {
    dlgLabel(tr ("Current &variant "));
    dlgComboBox(Variants, VDsel) {
      CurrentVariant = Variants[VDsel];
      setvariant(CurrentVariant);
      CollectPartData(CurrentVariant);
      GenerateList();
    }
    dlgStretch(1);
  }
  dlgListView ("", Lines, Selected);
  dlgHBoxLayout
  {
    dlgGroup(tr ("List type"))
    {
      dlgRadioButton(tr ("&Parts"), ListType) GeneratePartList ();
      dlgRadioButton(tr ("&Values"), ListType) GenerateValueList ();
      dlgCheckBox(tr ("List &attributes"), UseAttributes) {
        if (!UseAttributes) {
          NumParts = 0;
        }
        CollectPartData(CurrentVariant);
        GenerateList();
      }
    }
    dlgGroup (tr ("Output format"))
    {
      // 2008-10-09: Entries swapped for correct function.
      dlgRadioButton(tr ("&Text"), OutputFormat);
      // 2008-11-24 cwi: New format added.
      dlgRadioButton(tr ("&CSV"), OutputFormat);
      dlgRadioButton(tr ("&HTML"), OutputFormat);
      dlgRadioButton(tr ("&Digikey"), OutputFormat) {
        ListType = ltValues;
        UseAttributes = 1;
        GenerateList();
      };
    }
    dlgStretch(1);
  }
  dlgHBoxLayout  {
    dlgPushButton (tr ("+Vie&w"))    ViewList ();
    dlgPushButton (tr ("&Save...")) SaveList ();
    dlgPushButton (tr ("H&elp"))    DisplayHelp ();
    dlgPushButton (tr ("-Close"))   dlgAccept ();
    dlgStretch(1);
    dlgLabel("Version " + Version);
  }
};
